Dim strFolderProcessing As String = "C:\Configurator\Processing\"


Dim strFile As String = Dir(strFolderProcessing & "\*.csv*", vbNormal)    ' Any File
Dim strlatestFile As String = Nothing
Dim dtLast As Date
Dim strNewestFile As String = Nothing

'loop through Incomming files to find latest modified date
Do While strFile <> ""
	If FileDateTime(strFolderProcessing & strFile) > dtLast Then
		dtLast = FileDateTime(strFolderProcessing & strFile)
		strNewestFile = strFile
		strlatestFile = strFolderProcessing & strFile
	End If
	strFile = Dir()
Loop
If strlatestFile = "" Then
	Return
End If

Dim ReadCSV As New System.IO.StreamReader(strlatestFile)
Dim WordSets As New ArrayList()

Do While ReadCSV.Peek <> - 1
	WordSets.Add(ReadCSV.ReadLine.Split(","))
Loop

iProperties.Value("Summary", "Title") = WordSets.Item(3)(1)
iProperties.Value("Project", "Project") = WordSets.Item(1)(1)

iLogicVb.UpdateWhenDone = True

' Get the DXF translator Add-In.
Dim DXFAddIn As TranslatorAddIn
DXFAddIn = ThisApplication.ApplicationAddIns.ItemById("{C24E3AC4-122E-11D5-8E91-0010B541CD80}")
'Set a reference to the active document (the document to be published).
Dim oDocument As Document
oDocument = ThisApplication.ActiveDocument
Dim oContext As TranslationContext
oContext = ThisApplication.TransientObjects.CreateTranslationContext
oContext.Type = IOMechanismEnum.kFileBrowseIOMechanism
' Create a NameValueMap object
Dim oOptions As NameValueMap
oOptions = ThisApplication.TransientObjects.CreateNameValueMap
' Create a DataMedium object
Dim oDataMedium As DataMedium
oDataMedium = ThisApplication.TransientObjects.CreateDataMedium
' Check whether the translator has 'SaveCopyAs' options
If DXFAddIn.HasSaveCopyAsOptions(oDocument, oContext, oOptions) Then
Dim strIniFile As String
strIniFile = "\\srv-dc02\Aquatop\Mijn documenten\Product development\13_Configurator\LaserSettings.ini"
' Create the name-value that specifies the ini file to use.
oOptions.Value("Export_Acad_IniFile") = strIniFile
End If
'Set the destination file name
oDataMedium.FileName = "C:\Configurator\Output\" & iProperties.Value("Project", "Project")  &"\"& iProperties.Value("Project", "Project") &"_"& ThisDoc.FileName(False) & ".dxf"
'Publish document.
DXFAddIn.SaveCopyAs(oDocument, oContext, oOptions, oDataMedium)
'Launch the dxf file in whatever application Windows is set to open this document type with
